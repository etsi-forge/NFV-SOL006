module etsi-nfv {
  yang-version 1.1;
  namespace "urn:etsi:params:xml:ns:yang:etsi-nfv";
  prefix nfv;

  include etsi-nfv-common;
  include etsi-nfv-ns;
  include etsi-nfv-vnf;
  include etsi-nfv-pnf;

  organization
    "European Telecommunications Standards Institute (ETSI)";

  description
    "Network Function Virtualization Descriptors";

  revision 2019-03-18 {
    description
      "Initial revision.
       NSD and PNFD according to ETSI GS NFV-IFA 014 Ed261v252
       VNFD according to ETSI GS NFV-IFA 011 Ed261v254";
  }

  container nfv {
    uses vnfd;
    uses nsd;
    uses pnfd;
  }
}
